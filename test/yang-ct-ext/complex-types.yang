module complex-types {

       namespace "urn:ietf:params:xml:ns:yang:complex-types";
       prefix "ct";

       organization
           "Nokia Siemens Networks";

       contact
           "Bernd Linowski";

       description
           "This module defines extensions to model complex types
            and typed instance identifiers.";

       revision 2009-09-29 {
           description "Initial revision.";
       }


        extension complex-type {
            description "Defines a complex-type.";
            reference "chapter 2.2., complex-type extension statement";
            argument type-identifier {
                yin-element true;
            }
        }


        extension extends {
            description "Defines the base type of a complex-type.";
            reference "chapter 2.5., extends extension statement";
            argument base-type-identifier {
                yin-element true;
            }
        }

        extension abstract {
            description "Makes the complex-type abstract.";
            reference "chapter 2.6., complex-type extension statement";
            argument status;
        }


        extension instance {
            description "Declares an instance of the given complex type.";
            reference "chapter 2.3., instance extension statement";
            argument ct-instance-identifier {
                yin-element true;
            }
        }

        extension instance-list {
            description "Declares a list of instances of the given complex type";
            reference "chapter 2.4., instance-list extension statement";
            argument ct-instance-identifier {
                yin-element true;
            }
        }

        extension instance-type {
            description "Tells to which type instance the instance
                         identifier refers to.";
            reference "chapter 3.2., instance-type extension statement";
            argument target-type-identifier {
                yin-element true;
            }
        }


        feature complex-types {
            description "This feature indicates that the agent supports
                         complex types and instance identifiers.";
        }

   }
