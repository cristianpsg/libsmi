A DEFINITIONS ::= BEGIN

    IMPORTS
        MODULE-IDENTITY, OBJECT-TYPE, OBJECT-IDENTITY,
	mib-2, zeroDotZero
                FROM SNMPv2-SMI;
	

a MODULE-IDENTITY
        LAST-UPDATED "9403240002Z"
        ORGANIZATION "MIBs R Us"
        CONTACT-INFO "Fred Flintstone"
        DESCRIPTION  "An Example Module Identity"
        ::= { experimental 11999 0 }


a3 OBJECT IDENTIFIER ::= { a2 3 }
a2 OBJECT IDENTIFIER ::= { a1 2 }
a1 OBJECT IDENTIFIER ::= { 1 1 }


END
