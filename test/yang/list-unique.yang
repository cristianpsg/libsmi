module lists-unique {
	namespace "urn:test:lists";
	prefix "l";

    container c {
		list interface {
             key name;
             unique "l:test/name1 test/l:test2 c:name name";
             ordered-by user;

             min-elements  12;
             max-elements " 10";
             min-elements  "124 ";

             unique "name speed l:speed test/l:test1";

			 container test {
				 leaf name1 {
                     config false;
				     type string;
				 }
                 container test1 {
                 }
			 }
			 leaf name {
				 type empty;
			 }
			 leaf speed {
				 type enumeration {
				     enum 10m;
				     enum 100m;
				     enum auto;
				 }
			 }
			 leaf observed-speed {
				 type uint32;
				 config false;
			 }
		 }
    }
    
}
