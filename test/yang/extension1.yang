module "extension1"
{
	namespace "urn:smilib:ext";
 	prefix ext; 

	import extmod {
		prefix extmod;
	}	
    include extsubmod;

	organization jub; 
	contact jub;
	description "Extension test";
	reference "Siarhei Kuryla";

	extension ext1;
    
    ext:ext3;

    extmod:subext1 argument;

    ext:ext2 test2 {
        ext:ext4 test1 {
            ext:ext2;
            ext:subext1;
        }
    }

	extension ext2 {
		argument test;
		status current;
	}

    extension ext3 {
		status current;
	}

    extension ext4 {
		argument test {
            yin-element false;
        }
		status current;
        reference "Siarhei Kuryla";
        description "a test extension module";
	}

}
