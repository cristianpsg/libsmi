--
-- This SMIv1 module has been generated by smidump 0.2.14. Do not edit.
--

MAU-MIB DEFINITIONS ::= BEGIN

IMPORTS
    OBJECT-TYPE
        FROM RFC-1212
    TRAP-TYPE
        FROM RFC-1215
    Counter
        FROM RFC1155-SMI
    mib-2
        FROM RFC1213-MIB
    TruthValue
        FROM SNMPv2-TC;

mauMod OBJECT IDENTIFIER
    ::= { snmpDot3MauMgt 6 }

-- mauMod MODULE-IDENTITY
--     LAST-UPDATED "199908240400Z"
--     ORGANIZATION 
--         "IETF Ethernet Interfaces and Hub MIB
--          Working Group"
--     CONTACT-INFO 
--         "WG E-mail: hubmib@hprnd.rose.hp.com
--          To subscribe: hubmib-request@hprnd.rose.hp.com
--          
--                 Chair: Dan Romascanu
--                Postal: Lucent Technologies
--                        Atidim Technology Park, Bldg. 3
--                        Tel Aviv 61131
--                        Israel
--                   Tel: +972 3 645 8414, 6458458
--                   Fax: +972 3 648 7146
--                E-mail: dromasca@lucent.com
--          
--               Editors: Andrew Smith
--                Postal: Extreme Networks, Inc.
--                        10460 Bandley Drive
--                        Cupertino, CA 95014
--                        USA
--                   Tel: +1 408 579-2821
--                E-mail: andrew@extremenetworks.com
--          
--                        John Flick
--                Postal: Hewlett-Packard Company
--                        8000 Foothills Blvd. M/S 5557
--                       Roseville, CA 95747-5557
--                       USA
--                  Tel: +1 916 785 4018
--                  Fax: +1 916 785 1199
--               E-mail: johnf@rose.hp.com
--                       Kathryn de Graaf
--               Postal: Argon Networks
--                       25 Porter Road
--                       Littleton, MA  01460
--                       USA
--                  Tel: +1 978 486 0665 x163
--                  Fax: +1 978 486 9379
--               E-mail: kdegraaf@argon.com"
--     DESCRIPTION 
--         "Management information for 802.3 MAUs.
--          
--          The following reference is used throughout
--          this MIB module:
--          
--          [IEEE 802.3 Std] refers to
--             IEEE Std 802.3, 1998 Edition: 'Information
--             technology - Telecommunications and
--             information exchange between systems -
--             Local and metropolitan area networks -
--             Specific requirements - Part 3: Carrier
--             sense multiple access with collision
--             detection (CSMA/CD) access method and
--             physical layer specifications',
--             September 1998.
--          
--          Of particular interest is Clause 30, '10Mb/s,
--          100Mb/s and 1000Mb/s Management'."
--     REVISION    "199908240400Z"
--     DESCRIPTION 
--         "This version published as RFC 2668. Updated
--          to include support for 1000 Mb/sec
--          MAUs and flow control negotiation."
--     REVISION    "199710310000Z"
--     DESCRIPTION 
--         "This version published as RFC 2239."
--     REVISION    "199309300000Z"
--     DESCRIPTION 
--         "Initial version, published as RFC 1515."
--     ::= { snmpDot3MauMgt 6 }


JackType ::=
    INTEGER { other(1), rj45(2), rj45S(3), db9(4), bnc(5), fAUI(6), 
                    mAUI(7), fiberSC(8), fiberMIC(9), fiberST(10), 
                    telco(11), mtrj(12), hssdc(13) }

-- JackType ::= TEXTUAL-CONVENTION
--     STATUS      mandatory
--     DESCRIPTION 
--         "Common enumeration values for repeater
--          and interface MAU jack types."
--     SYNTAX      INTEGER
--                   { other(1), rj45(2), rj45S(3), db9(4), bnc(5), 
--                     fAUI(6), mAUI(7), fiberSC(8), fiberMIC(9), 
--                     fiberST(10), telco(11), mtrj(12), hssdc(13) }

snmpDot3MauMgt OBJECT IDENTIFIER
    ::= { mib-2 26 }

snmpDot3MauTraps OBJECT IDENTIFIER
    ::= { snmpDot3MauMgt 0 }

dot3RpMauBasicGroup OBJECT IDENTIFIER
    ::= { snmpDot3MauMgt 1 }

rpMauTable OBJECT-TYPE
    SYNTAX      SEQUENCE OF RpMauEntry
    ACCESS      not-accessible
    STATUS      mandatory
    DESCRIPTION 
        "Table of descriptive and status information
         about the MAU(s) attached to the ports of a
         repeater."
    ::= { dot3RpMauBasicGroup 1 }

rpMauEntry OBJECT-TYPE
    SYNTAX      RpMauEntry
    ACCESS      not-accessible
    STATUS      mandatory
    DESCRIPTION 
        "An entry in the table, containing information
         about a single MAU."
    INDEX       { rpMauGroupIndex, rpMauPortIndex, rpMauIndex }
    ::= { rpMauTable 1 }

RpMauEntry ::= SEQUENCE {
    rpMauGroupIndex                 INTEGER,
    rpMauPortIndex                  INTEGER,
    rpMauIndex                      INTEGER,
    rpMauType                       OBJECT IDENTIFIER,
    rpMauStatus                     INTEGER,
    rpMauMediaAvailable             INTEGER,
    rpMauMediaAvailableStateExits   Counter,
    rpMauJabberState                INTEGER,
    rpMauJabberingStateEnters       Counter,
    rpMauFalseCarriers              Counter
}

rpMauGroupIndex OBJECT-TYPE
    SYNTAX      INTEGER (1..2147483647)
    ACCESS      read-only
    STATUS      mandatory
    DESCRIPTION 
        "This variable uniquely identifies the group
         containing the port to which the MAU described
         by this entry is connected.
         
         Note:  In practice, a group will generally be
         a field-replaceable unit (i.e., module, card,
         or board) that can fit in the physical system
         enclosure, and the group number will correspond
         to a number marked on the physical enclosure.
         
         The group denoted by a particular value of this
         object is the same as the group denoted by the
         same value of rptrGroupIndex."
--     REFERENCE   
--         "Reference RFC 2108, rptrGroupIndex."
    ::= { rpMauEntry 1 }

rpMauPortIndex OBJECT-TYPE
    SYNTAX      INTEGER (1..2147483647)
    ACCESS      read-only
    STATUS      mandatory
    DESCRIPTION 
        "This variable uniquely identifies the repeater
         port within group rpMauGroupIndex to which the
         MAU described by this entry is connected."
--     REFERENCE   
--         "Reference RFC 2108, rptrPortIndex."
    ::= { rpMauEntry 2 }

rpMauIndex OBJECT-TYPE
    SYNTAX      INTEGER (1..2147483647)
    ACCESS      read-only
    STATUS      mandatory
    DESCRIPTION 
        "This variable uniquely identifies the MAU
         described by this entry from among other
         MAUs connected to the same port
         (rpMauPortIndex)."
--     REFERENCE   
--         "[IEEE 802.3 Std], 30.5.1.1.1, aMAUID."
    ::= { rpMauEntry 3 }

rpMauType OBJECT-TYPE
    SYNTAX      OBJECT IDENTIFIER
    ACCESS      read-only
    STATUS      mandatory
    DESCRIPTION 
        "This object identifies the MAU type.  An
         initial set of MAU types are defined above.  The
         assignment of OBJECT IDENTIFIERs to new types of
         MAUs is managed by the IANA.  If the MAU type is
         unknown, the object identifier
         
         unknownMauType OBJECT IDENTIFIER ::= { 0 0 }
         
         is returned.  Note that unknownMauType is a
         syntactically valid object identifier, and any
         conformant implementation of ASN.1 and the BER
         must be able to generate and recognize this
         value."
--     REFERENCE   
--         "[IEEE 802.3 Std], 30.5.1.1.2, aMAUType."
    ::= { rpMauEntry 4 }

rpMauStatus OBJECT-TYPE
    SYNTAX      INTEGER { other(1), unknown(2), operational(3), 
                    standby(4), shutdown(5), reset(6) }
    ACCESS      read-write
    STATUS      mandatory
    DESCRIPTION 
        "The current state of the MAU.  This object MAY
         be implemented as a read-only object by those
         agents and MAUs that do not implement software
         control of the MAU state.  Some agents may not
         support setting the value of this object to some
         of the enumerated values.
         
         The value other(1) is returned if the MAU is in
         a state other than one of the states 2 through
         6.
         The value unknown(2) is returned when the MAU's
         true state is unknown; for example, when it is
         being initialized.
         
         A MAU in the operational(3) state is fully
         functional, operates, and passes signals to its
         attached DTE or repeater port in accordance to
         its specification.
         
         A MAU in standby(4) state forces DI and CI to
         idle and the media transmitter to idle or fault,
         if supported.  Standby(4) mode only applies to
         link type MAUs.  The state of
         rpMauMediaAvailable is unaffected.
         
         A MAU in shutdown(5) state assumes the same
         condition on DI, CI, and the media transmitter
         as though it were powered down or not connected.
         The MAU MAY return other(1) value for the
         rpMauJabberState and rpMauMediaAvailable objects
         when it is in this state.  For an AUI, this
         state will remove power from the AUI.
         
         Setting this variable to the value reset(6)
         resets the MAU in the same manner as a
         power-off, power-on cycle of at least one-half
         second would.  The agent is not required to
         return the value reset (6).
         
         Setting this variable to the value
         operational(3), standby(4), or shutdown(5)
         causes the MAU to assume the respective state
         except that setting a mixing-type MAU or an AUI
         to standby(4) will cause the MAU to enter the
         shutdown state."
--     REFERENCE   
--         "[IEEE 802.3 Std], 30.5.1.1.7, aMAUAdminState,
--          30.5.1.2.2, acMAUAdminControl, and 30.5.1.2.1,
--          acResetMAU."
    ::= { rpMauEntry 5 }

rpMauMediaAvailable OBJECT-TYPE
    SYNTAX      INTEGER { other(1), unknown(2), available(3), 
                    notAvailable(4), remoteFault(5), invalidSignal(6), 
                    remoteJabber(7), remoteLinkLoss(8), remoteTest(9), 
                    offline(10), autoNegError(11) }
    ACCESS      read-only
    STATUS      mandatory
    DESCRIPTION 
        "If the MAU is a link or fiber type (FOIRL,
         10BASE-T, 10BASE-F) then this is equivalent to
         the link test fail state/low light function.
         For an AUI or a coax (including broadband) MAU
         this indicates whether or not loopback is
         detected on the DI circuit.  The value of this
         attribute persists between packets for MAU types
         AUI, 10BASE5, 10BASE2, 10BROAD36, and 10BASE-FP.
         
         The value other(1) is returned if the
         mediaAvailable state is not one of 2 through 11.
         
         The value unknown(2) is returned when the MAU's
         true state is unknown; for example, when it is
         being initialized.  At power-up or following a
         reset, the value of this attribute will be
         unknown for AUI, coax, and 10BASE-FP MAUs.  For
         these MAUs loopback will be tested on each
         transmission during which no collision is
         detected.  If DI is receiving input when DO
         returns to IDL after a transmission and there
         has been no collision during the transmission
         then loopback will be detected.  The value of
         this attribute will only change during
         non-collided transmissions for AUI, coax, and
         10BASE-FP MAUs.
         
         For 100Mbps and 1000Mbps MAUs, the enumerations
         match the states within the respective link
         integrity state diagrams, fig 32-16, 23-12 and
         24-15 of sections 32, 23 and 24 of [16].  Any
         MAU which implements management of
         auto-negotiation will map remote fault
         indication to remote fault.
         
         The value available(3) indicates that the link,
         light, or loopback is normal.  The value
         notAvailable(4) indicates link loss, low light,
         or no loopback.
         The value remoteFault(5) indicates that a fault
         has been detected at the remote end of the link.
         This value applies to 10BASE-FB, 100BASE-T4 Far
         End Fault Indication and non-specified remote
         faults from a system running auto-negotiation.
         The values remoteJabber(7), remoteLinkLoss(8),
         and remoteTest(9) SHOULD be used instead of
         remoteFault(5) where the reason for remote fault
         is identified in the remote signaling protocol.
         
         The value invalidSignal(6) indicates that an
         invalid signal has been received from the other
         end of the link.  InvalidSignal(6) applies only
         to MAUs of type 10BASE-FB.
         
         Where an IEEE Std 802.3u-1995 clause 22 MII
         is present, a logic one in the remote fault bit
         (reference section 22.2.4.2.8 of that document)
         maps to the value remoteFault(5), and a logic
         zero in the link status bit (reference section
         22.2.4.2.10 of that document) maps to the value
         notAvailable(4).  The value notAvailable(4)
         takes precedence over the value remoteFault(5).
         
         Any MAU that implements management of clause 37
         Auto-Negotiation will map the received Remote
         Fault (RF1 and RF2) bit values for Offline to
         offline(10), Link Failure to remoteFault(5) and
         Auto-Negotiation Error to autoNegError(11)."
--     REFERENCE   
--         "[IEEE 802.3 Std], 30.5.1.1.4, aMediaAvailable."
    ::= { rpMauEntry 6 }

rpMauMediaAvailableStateExits OBJECT-TYPE
    SYNTAX      Counter
    ACCESS      read-only
    STATUS      mandatory
    DESCRIPTION 
        "A count of the number of times that
         rpMauMediaAvailable for this MAU instance leaves
         the state available(3).
         
         Discontinuities in the value of this counter can
         occur at re-initialization of the management
         system, and at other times as indicated by the
         value of rptrMonitorPortLastChange."
--     REFERENCE   
--         "[IEEE 802.3 Std], 30.5.1.1.5,
--          aLoseMediaCounter.
--          RFC 2108, rptrMonitorPortLastChange"
    ::= { rpMauEntry 7 }

rpMauJabberState OBJECT-TYPE
    SYNTAX      INTEGER { other(1), unknown(2), noJabber(3), 
                    jabbering(4) }
    ACCESS      read-only
    STATUS      mandatory
    DESCRIPTION 
        "The value other(1) is returned if the jabber
         state is not 2, 3, or 4.  The agent MUST always
         return other(1) for MAU type dot3MauTypeAUI.
         
         The value unknown(2) is returned when the MAU's
         true state is unknown; for example, when it is
         being initialized.
         
         If the MAU is not jabbering the agent returns
         noJabber(3).  This is the 'normal' state.
         
         If the MAU is in jabber state the agent returns
         the jabbering(4) value."
--     REFERENCE   
--         "[IEEE 802.3 Std], 30.5.1.1.6,
--          aJabber.jabberFlag."
    ::= { rpMauEntry 8 }

rpMauJabberingStateEnters OBJECT-TYPE
    SYNTAX      Counter
    ACCESS      read-only
    STATUS      mandatory
    DESCRIPTION 
        "A count of the number of times that
         mauJabberState for this MAU instance enters the
         state jabbering(4).  For MAUs of type
         dot3MauTypeAUI, dot3MauType100BaseT4,
         dot3MauType100BaseTX, dot3MauType100BaseFX and
             all 1000Mbps types, this counter will always
             indicate zero.
         
             Discontinuities in the value of this counter
             can occur at re-initialization of the
             management system, and at other times as
             indicated by the value of
             rptrMonitorPortLastChange."
--     REFERENCE   
--         "[IEEE 802.3 Std], 30.5.1.1.6,
--          aJabber.jabberCounter.
--          RFC 2108, rptrMonitorPortLastChange"
    ::= { rpMauEntry 9 }

rpMauFalseCarriers OBJECT-TYPE
    SYNTAX      Counter
    ACCESS      read-only
    STATUS      mandatory
    DESCRIPTION 
        "A count of the number of false carrier events
         during IDLE in 100BASE-X links.  This counter
         does not increment at the symbol rate.  It can
         increment after a valid carrier completion at a
         maximum rate of once per 100 ms until the next
         carrier event.
         
         This counter increments only for MAUs of type
         dot3MauType100BaseT4, dot3MauType100BaseTX, and
         dot3MauType100BaseFX and all 1000Mbps types.
         For all other MAU types, this counter will
         always indicate zero.
         
         The approximate minimum time for rollover of
         this counter is 7.4 hours.
         
         Discontinuities in the value of this counter can
         occur at re-initialization of the management
         system, and at other times as indicated by the
         value of rptrMonitorPortLastChange."
--     REFERENCE   
--         "[IEEE 802.3 Std], 30.5.1.1.10, aFalseCarriers.
--          RFC 2108, rptrMonitorPortLastChange"
    ::= { rpMauEntry 10 }

rpJackTable OBJECT-TYPE
    SYNTAX      SEQUENCE OF RpJackEntry
    ACCESS      not-accessible
    STATUS      mandatory
    DESCRIPTION 
        "Information about the external jacks attached
         to MAUs attached to the ports of a repeater."
    ::= { dot3RpMauBasicGroup 2 }

rpJackEntry OBJECT-TYPE
    SYNTAX      RpJackEntry
    ACCESS      not-accessible
    STATUS      mandatory
    DESCRIPTION 
        "An entry in the table, containing information
         about a particular jack."
    INDEX       { rpMauGroupIndex, rpMauPortIndex, rpMauIndex, 
                  rpJackIndex }
    ::= { rpJackTable 1 }

RpJackEntry ::= SEQUENCE {
    rpJackIndex     INTEGER,
    rpJackType      JackType
}

rpJackIndex OBJECT-TYPE
    SYNTAX      INTEGER (1..2147483647)
    ACCESS      not-accessible
    STATUS      mandatory
    DESCRIPTION 
        "This variable uniquely identifies the jack
         described by this entry from among other jacks
         attached to the same MAU (rpMauIndex)."
    ::= { rpJackEntry 1 }

rpJackType OBJECT-TYPE
    SYNTAX      JackType
    ACCESS      read-only
    STATUS      mandatory
    DESCRIPTION 
        "The jack connector type, as it appears on the
         outside of the system."
    ::= { rpJackEntry 2 }

dot3IfMauBasicGroup OBJECT IDENTIFIER
    ::= { snmpDot3MauMgt 2 }

ifMauTable OBJECT-TYPE
    SYNTAX      SEQUENCE OF IfMauEntry
    ACCESS      not-accessible
    STATUS      mandatory
    DESCRIPTION 
        "Table of descriptive and status information
         about MAU(s) attached to an interface."
    ::= { dot3IfMauBasicGroup 1 }

ifMauEntry OBJECT-TYPE
    SYNTAX      IfMauEntry
    ACCESS      not-accessible
    STATUS      mandatory
    DESCRIPTION 
        "An entry in the table, containing information
         about a single MAU."
    INDEX       { ifMauIfIndex, ifMauIndex }
    ::= { ifMauTable 1 }

IfMauEntry ::= SEQUENCE {
    ifMauIfIndex                    INTEGER,
    ifMauIndex                      INTEGER,
    ifMauType                       OBJECT IDENTIFIER,
    ifMauStatus                     INTEGER,
    ifMauMediaAvailable             INTEGER,
    ifMauMediaAvailableStateExits   Counter,
    ifMauJabberState                INTEGER,
    ifMauJabberingStateEnters       Counter,
    ifMauFalseCarriers              Counter,
    ifMauTypeList                   INTEGER,
    ifMauDefaultType                OBJECT IDENTIFIER,
    ifMauAutoNegSupported           TruthValue,
    ifMauTypeListBits               OCTET STRING
}

ifMauIfIndex OBJECT-TYPE
    SYNTAX      INTEGER (1..2147483647)
    ACCESS      read-only
    STATUS      mandatory
    DESCRIPTION 
        "This variable uniquely identifies the interface
         to which the MAU described by this entry is
         connected."
--     REFERENCE   
--         "RFC 1213, ifIndex"
    ::= { ifMauEntry 1 }

ifMauIndex OBJECT-TYPE
    SYNTAX      INTEGER (1..2147483647)
    ACCESS      read-only
    STATUS      mandatory
    DESCRIPTION 
        "This variable uniquely identifies the MAU
         described by this entry from among other MAUs
         connected to the same interface (ifMauIfIndex)."
--     REFERENCE   
--         "[IEEE 802.3 Std], 30.5.1.1.1, aMAUID."
    ::= { ifMauEntry 2 }

ifMauType OBJECT-TYPE
    SYNTAX      OBJECT IDENTIFIER
    ACCESS      read-only
    STATUS      mandatory
    DESCRIPTION 
        "This object identifies the MAU type.  An
         initial set of MAU types are defined above.  The
         assignment of OBJECT IDENTIFIERs to new types of
         MAUs is managed by the IANA.  If the MAU type is
         unknown, the object identifier
         
         unknownMauType OBJECT IDENTIFIER ::= { 0 0 }
         
         is returned.  Note that unknownMauType is a
         syntactically valid object identifier, and any
         conformant implementation of ASN.1 and the BER
         must be able to generate and recognize this
         value.
         
         This object represents the operational type of
         the MAU, as determined by either (1) the result
         of the auto-negotiation function or (2) if
         auto-negotiation is not enabled or is not
         implemented for this MAU, by the value of the
         object ifMauDefaultType.  In case (2), a set to
         the object ifMauDefaultType will force the MAU
         into the new operating mode."
--     REFERENCE   
--         "[IEEE 802.3 Std], 30.5.1.1.2, aMAUType."
    ::= { ifMauEntry 3 }

ifMauStatus OBJECT-TYPE
    SYNTAX      INTEGER { other(1), unknown(2), operational(3), 
                    standby(4), shutdown(5), reset(6) }
    ACCESS      read-write
    STATUS      mandatory
    DESCRIPTION 
        "The current state of the MAU.  This object MAY
         be implemented as a read-only object by those
         agents and MAUs that do not implement software
         control of the MAU state.  Some agents may not
         support setting the value of this object to some
         of the enumerated values.
         
         The value other(1) is returned if the MAU is in
         a state other than one of the states 2 through
         6.
         
         The value unknown(2) is returned when the MAU's
         true state is unknown; for example, when it is
         being initialized.
         A MAU in the operational(3) state is fully
         functional, operates, and passes signals to its
         attached DTE or repeater port in accordance to
         its specification.
         
         A MAU in standby(4) state forces DI and CI to
         idle and the media transmitter to idle or fault,
         if supported.  Standby(4) mode only applies to
         link type MAUs.  The state of
         ifMauMediaAvailable is unaffected.
         
         A MAU in shutdown(5) state assumes the same
         condition on DI, CI, and the media transmitter
         as though it were powered down or not connected.
         The MAU MAY return other(1) value for the
         ifMauJabberState and ifMauMediaAvailable objects
         when it is in this state.  For an AUI, this
         state will remove power from the AUI.
         
         Setting this variable to the value reset(6)
         resets the MAU in the same manner as a
         power-off, power-on cycle of at least one-half
         second would.  The agent is not required to
         return the value reset (6).
         
         Setting this variable to the value
         operational(3), standby(4), or shutdown(5)
         causes the MAU to assume the respective state
         except that setting a mixing-type MAU or an AUI
         to standby(4) will cause the MAU to enter the
         shutdown state."
--     REFERENCE   
--         "[IEEE 802.3 Std], 30.5.1.1.7, aMAUAdminState,
--          30.5.1.2.2, acMAUAdminControl, and 30.5.1.2.1,
--          acResetMAU."
    ::= { ifMauEntry 4 }

ifMauMediaAvailable OBJECT-TYPE
    SYNTAX      INTEGER { other(1), unknown(2), available(3), 
                    notAvailable(4), remoteFault(5), invalidSignal(6), 
                    remoteJabber(7), remoteLinkLoss(8), remoteTest(9), 
                    offline(10), autoNegError(11) }
    ACCESS      read-only
    STATUS      mandatory
    DESCRIPTION 
        "If the MAU is a link or fiber type (FOIRL,
         10BASE-T, 10BASE-F) then this is equivalent to
         the link test fail state/low light function.
         For an AUI or a coax (including broadband) MAU
         this indicates whether or not loopback is
         detected on the DI circuit.  The value of this
         attribute persists between packets for MAU types
         AUI, 10BASE5, 10BASE2, 10BROAD36, and 10BASE-FP.
         
         The value other(1) is returned if the
         mediaAvailable state is not one of 2 through 11.
         
         The value unknown(2) is returned when the MAU's
         true state is unknown; for example, when it is
         being initialized.  At power-up or following a
         reset, the value of this attribute will be
         unknown for AUI, coax, and 10BASE-FP MAUs.  For
         these MAUs loopback will be tested on each
         transmission during which no collision is
         detected.  If DI is receiving input when DO
         returns to IDL after a transmission and there
         has been no collision during the transmission
         then loopback will be detected.  The value of
         this attribute will only change during
         non-collided transmissions for AUI, coax, and
         10BASE-FP MAUs.
         
         For 100Mbps and 1000Mbps MAUs, the enumerations
         match the states within the respective link
         integrity state diagrams, fig 32-16, 23-12 and
         24-15 of sections 32, 23 and 24 of [16].  Any
         MAU which implements management of
         auto-negotiation will map remote fault
         indication to remote fault.
         
         The value available(3) indicates that the link,
         light, or loopback is normal.  The value
         notAvailable(4) indicates link loss, low light,
         or no loopback.
         
         The value remoteFault(5) indicates that a fault
         has been detected at the remote end of the link.
         This value applies to 10BASE-FB, 100BASE-T4 Far
         End Fault Indication and non-specified remote
         faults from a system running auto-negotiation.
         The values remoteJabber(7), remoteLinkLoss(8),
         and remoteTest(9) SHOULD be used instead of
         remoteFault(5) where the reason for remote fault
         is identified in the remote signaling protocol.
         
         The value invalidSignal(6) indicates that an
         invalid signal has been received from the other
         end of the link.  InvalidSignal(6) applies only
         to MAUs of type 10BASE-FB.
         
         Where an IEEE Std 802.3u-1995 clause 22 MII
         is present, a logic one in the remote fault bit
         (reference section 22.2.4.2.8 of that document)
         maps to the value remoteFault(5), and a logic
         zero in the link status bit (reference section
         22.2.4.2.10 of that document) maps to the value
         notAvailable(4).  The value notAvailable(4)
         takes precedence over the value remoteFault(5).
         
         Any MAU that implements management of clause 37
         Auto-Negotiation will map the received RF1 and
         RF2 bit values for Offline to offline(10), Link
         Failure to remoteFault(5) and Auto-Negotiation
         Error to autoNegError(11)."
--     REFERENCE   
--         "[IEEE 802.3 Std], 30.5.1.1.4, aMediaAvailable."
    ::= { ifMauEntry 5 }

ifMauMediaAvailableStateExits OBJECT-TYPE
    SYNTAX      Counter
    ACCESS      read-only
    STATUS      mandatory
    DESCRIPTION 
        "A count of the number of times that
         ifMauMediaAvailable for this MAU instance leaves
         the state available(3).
         Discontinuities in the value of this counter can
         occur at re-initialization of the management
         system, and at other times as indicated by the
         value of ifCounterDiscontinuityTime."
--     REFERENCE   
--         "[IEEE 802.3 Std], 30.5.1.1.5,
--          aLoseMediaCounter.
--          RFC 2233, ifCounterDiscontinuityTime."
    ::= { ifMauEntry 6 }

ifMauJabberState OBJECT-TYPE
    SYNTAX      INTEGER { other(1), unknown(2), noJabber(3), 
                    jabbering(4) }
    ACCESS      read-only
    STATUS      mandatory
    DESCRIPTION 
        "The value other(1) is returned if the jabber
         state is not 2, 3, or 4.  The agent MUST always
         return other(1) for MAU type dot3MauTypeAUI.
         
         The value unknown(2) is returned when the MAU's
         true state is unknown; for example, when it is
         being initialized.
         
         If the MAU is not jabbering the agent returns
         noJabber(3).  This is the 'normal' state.
         
         If the MAU is in jabber state the agent returns
         the jabbering(4) value."
--     REFERENCE   
--         "[IEEE 802.3 Std], 30.5.1.1.6,
--          aJabber.jabberFlag."
    ::= { ifMauEntry 7 }

ifMauJabberingStateEnters OBJECT-TYPE
    SYNTAX      Counter
    ACCESS      read-only
    STATUS      mandatory
    DESCRIPTION 
        "A count of the number of times that
         mauJabberState for this MAU instance enters the
         state jabbering(4). This counter will always
         indicate zero for MAUs of type dot1MauTypeAUI
         and those of speeds above 10Mbps.
         
         Discontinuities in the value of this counter can
         occur at re-initialization of the management
         system, and at other times as indicated by the
         value of ifCounterDiscontinuityTime."
--     REFERENCE   
--         "[IEEE 802.3 Std], 30.5.1.1.6,
--          aJabber.jabberCounter.
--          RFC 2233, ifCounterDiscontinuityTime."
    ::= { ifMauEntry 8 }

ifMauFalseCarriers OBJECT-TYPE
    SYNTAX      Counter
    ACCESS      read-only
    STATUS      mandatory
    DESCRIPTION 
        "A count of the number of false carrier events
         during IDLE in 100BASE-X and 1000BASE-X links.
         
         For all other MAU types, this counter will
         always indicate zero. This counter does not
         increment at the symbol rate.
         
         It can increment after a valid carrier
         completion at a maximum rate of once per 100 ms
         for 100BASE-X and once per 10us for 1000BASE-X
         until the next CarrierEvent.
         
         Discontinuities in the value of this counter can
         occur at re-initialization of the management
         system, and at other times as indicated by the
         value of ifCounterDiscontinuityTime."
--     REFERENCE   
--         "[IEEE 802.3 Std], 30.5.1.1.10, aFalseCarriers.
--          RFC 2233, ifCounterDiscontinuityTime."
    ::= { ifMauEntry 9 }

ifMauTypeList OBJECT-TYPE
    SYNTAX      INTEGER
    ACCESS      read-only
    STATUS      deprecated
    DESCRIPTION 
        "********* THIS OBJECT IS DEPRECATED **********
         
         A value that uniquely identifies the set of
         possible IEEE 802.3 types that the MAU could be.
         The value is a sum which initially takes the
         value zero.  Then, for each type capability of
         this MAU, 2 raised to the power noted below is
         added to the sum. For example, a MAU which has
         the capability to be only 10BASE-T would have a
         value of 512 (2**9).  In contrast, a MAU which
         supports both 10Base-T (full duplex) and
         100BASE-TX (full duplex) would have a value of
         ((2**11) + (2**16)) or 67584.
         
         The powers of 2 assigned to the capabilities are
         these:
         
         Power  Capability
           0      other or unknown
           1      AUI
           2      10BASE-5
           3      FOIRL
           4      10BASE-2
           5      10BASE-T duplex mode unknown
           6      10BASE-FP
           7      10BASE-FB
           8      10BASE-FL duplex mode unknown
           9      10BROAD36
          10      10BASE-T  half duplex mode
          11      10BASE-T  full duplex mode
          12      10BASE-FL half duplex mode
          13      10BASE-FL full duplex mode
          14      100BASE-T4
          15      100BASE-TX half duplex mode
          16      100BASE-TX full duplex mode
          17      100BASE-FX half duplex mode
          18      100BASE-FX full duplex mode
          19      100BASE-T2 half duplex mode
          20      100BASE-T2 full duplex mode
         
         If auto-negotiation is present on this MAU, this
         object will map to ifMauAutoNegCapability.
         
         This object has been deprecated in favour of
         ifMauTypeListBits."
    ::= { ifMauEntry 10 }

ifMauDefaultType OBJECT-TYPE
    SYNTAX      OBJECT IDENTIFIER
    ACCESS      read-write
    STATUS      mandatory
    DESCRIPTION 
        "This object identifies the default
         administrative baseband MAU type, to be used in
         conjunction with the operational MAU type
         denoted by ifMauType.
         
         The set of possible values for this object is
         the same as the set defined for the ifMauType
         object.
         
         This object represents the
         administratively-configured type of the MAU.  If
         auto-negotiation is not enabled or is not
         implemented for this MAU, the value of this
         object determines the operational type of the
         MAU.  In this case, a set to this object will
         force the MAU into the specified operating mode.
         
         If auto-negotiation is implemented and enabled
         for this MAU, the operational type of the MAU
         is determined by auto-negotiation, and the value
         of this object denotes the type to which the MAU
         will automatically revert if/when
         auto-negotiation is later disabled.
         
         NOTE TO IMPLEMENTORS:  It may be necessary to
         provide for underlying hardware implementations
         which do not follow the exact behavior specified
         above.  In particular, when
         ifMauAutoNegAdminStatus transitions from enabled
         to disabled, the agent implementation MUST
         ensure that the operational type of the MAU (as
         reported by ifMauType) correctly transitions to
         the value specified by this object, rather than
         continuing to operate at the value earlier
         determined by the auto-negotiation function."
--     REFERENCE   
--         "[IEEE 802.3 Std], 30.5.1.1.1, aMAUID, and
--          22.2.4.1.4."
    ::= { ifMauEntry 11 }

ifMauAutoNegSupported OBJECT-TYPE
    SYNTAX      TruthValue
    ACCESS      read-only
    STATUS      mandatory
    DESCRIPTION 
        "This object indicates whether or not
         auto-negotiation is supported on this MAU."
    ::= { ifMauEntry 12 }

ifMauTypeListBits OBJECT-TYPE
    SYNTAX      OCTET STRING
--                   { bOther(0), bAUI(1), b10base5(2), bFoirl(3), 
--                     b10base2(4), b10baseT(5), b10baseFP(6), 
--                     b10baseFB(7), b10baseFL(8), b10broad36(9), 
--                     b10baseTHD(10), b10baseTFD(11), b10baseFLHD(12), 
--                     b10baseFLFD(13), b100baseT4(14), b100baseTXHD(15), 
--                     b100baseTXFD(16), b100baseFXHD(17), 
--                     b100baseFXFD(18), b100baseT2HD(19), 
--                     b100baseT2FD(20), b1000baseXHD(21), 
--                     b1000baseXFD(22), b1000baseLXHD(23), 
--                     b1000baseLXFD(24), b1000baseSXHD(25), 
--                     b1000baseSXFD(26), b1000baseCXHD(27), 
--                     b1000baseCXFD(28), b1000baseTHD(29), 
--                     b1000baseTFD(30) }
    ACCESS      read-only
    STATUS      mandatory
    DESCRIPTION 
        "A value that uniquely identifies the set of
         possible IEEE 802.3 types that the MAU could be.
         If auto-negotiation is present on this MAU, this
         object will map to ifMauAutoNegCapability.
         
         Note that this MAU may be capable of operating
         as a MAU type that is beyond the scope of this
         MIB.  This is indicated by returning the
         bit value bOther in addition to any bit values
         for capabilities that are listed above."
    ::= { ifMauEntry 13 }

ifJackTable OBJECT-TYPE
    SYNTAX      SEQUENCE OF IfJackEntry
    ACCESS      not-accessible
    STATUS      mandatory
    DESCRIPTION 
        "Information about the external jacks attached
         to MAUs attached to an interface."
    ::= { dot3IfMauBasicGroup 2 }

ifJackEntry OBJECT-TYPE
    SYNTAX      IfJackEntry
    ACCESS      not-accessible
    STATUS      mandatory
    DESCRIPTION 
        "An entry in the table, containing information
         about a particular jack."
    INDEX       { ifMauIfIndex, ifMauIndex, ifJackIndex }
    ::= { ifJackTable 1 }

IfJackEntry ::= SEQUENCE {
    ifJackIndex     INTEGER,
    ifJackType      JackType
}

ifJackIndex OBJECT-TYPE
    SYNTAX      INTEGER (1..2147483647)
    ACCESS      not-accessible
    STATUS      mandatory
    DESCRIPTION 
        "This variable uniquely identifies the jack
         described by this entry from among other jacks
         attached to the same MAU."
    ::= { ifJackEntry 1 }

ifJackType OBJECT-TYPE
    SYNTAX      JackType
    ACCESS      read-only
    STATUS      mandatory
    DESCRIPTION 
        "The jack connector type, as it appears on the
         outside of the system."
    ::= { ifJackEntry 2 }

dot3BroadMauBasicGroup OBJECT IDENTIFIER
    ::= { snmpDot3MauMgt 3 }

broadMauBasicTable OBJECT-TYPE
    SYNTAX      SEQUENCE OF BroadMauBasicEntry
    ACCESS      not-accessible
    STATUS      deprecated
    DESCRIPTION 
        "********* THIS OBJECT IS DEPRECATED **********
         
         Table of descriptive and status information
         about the broadband MAUs connected to
         interfaces."
    ::= { dot3BroadMauBasicGroup 1 }

broadMauBasicEntry OBJECT-TYPE
    SYNTAX      BroadMauBasicEntry
    ACCESS      not-accessible
    STATUS      deprecated
    DESCRIPTION 
        "********* THIS OBJECT IS DEPRECATED **********
         
         An entry in the table, containing information
         about a single broadband MAU."
    INDEX       { broadMauIfIndex, broadMauIndex }
    ::= { broadMauBasicTable 1 }

BroadMauBasicEntry ::= SEQUENCE {
    broadMauIfIndex             INTEGER,
    broadMauIndex               INTEGER,
    broadMauXmtRcvSplitType     INTEGER,
    broadMauXmtCarrierFreq      INTEGER,
    broadMauTranslationFreq     INTEGER
}

broadMauIfIndex OBJECT-TYPE
    SYNTAX      INTEGER (1..2147483647)
    ACCESS      read-only
    STATUS      deprecated
    DESCRIPTION 
        "********* THIS OBJECT IS DEPRECATED **********
         
         This variable uniquely identifies the interface
         to which the MAU described by this entry is
         connected."
--     REFERENCE   
--         "Reference RFC 1213, ifIndex."
    ::= { broadMauBasicEntry 1 }

broadMauIndex OBJECT-TYPE
    SYNTAX      INTEGER (1..2147483647)
    ACCESS      read-only
    STATUS      deprecated
    DESCRIPTION 
        "********* THIS OBJECT IS DEPRECATED **********
         
         This variable uniquely identifies the MAU
         connected to interface broadMauIfIndex that is
         described by this entry."
--     REFERENCE   
--         "[IEEE 802.3 Std], 30.5.1.1.1, aMAUID."
    ::= { broadMauBasicEntry 2 }

broadMauXmtRcvSplitType OBJECT-TYPE
    SYNTAX      INTEGER { other(1), single(2), dual(3) }
    ACCESS      read-only
    STATUS      deprecated
    DESCRIPTION 
        "********* THIS OBJECT IS DEPRECATED **********
         
         This object indicates the type of frequency
         multiplexing/cabling system used to separate the
         transmit and receive paths for the 10BROAD36
         MAU.
         
         The value other(1) is returned if the split type
         is not either single or dual.
         
         The value single(2) indicates a single cable
         system.  The value dual(3) indicates a dual
         cable system, offset normally zero."
--     REFERENCE   
--         "[IEEE 802.3 Std], 30.5.1.1.8,
--          aBbMAUXmitRcvSplitType."
    ::= { broadMauBasicEntry 3 }

broadMauXmtCarrierFreq OBJECT-TYPE
    SYNTAX      INTEGER
    ACCESS      read-only
    STATUS      deprecated
    DESCRIPTION 
        "********* THIS OBJECT IS DEPRECATED **********
         
         This variable indicates the transmit carrier
         frequency of the 10BROAD36 MAU in MHz/4; that
         is, in units of 250 kHz."
--     REFERENCE   
--         "[IEEE 802.3 Std], 30.5.1.1.9,
--          aBroadbandFrequencies.xmitCarrierFrequency."
    ::= { broadMauBasicEntry 4 }

broadMauTranslationFreq OBJECT-TYPE
    SYNTAX      INTEGER
    ACCESS      read-only
    STATUS      deprecated
    DESCRIPTION 
        "********* THIS OBJECT IS DEPRECATED **********
         
         This variable indicates the translation offset
         frequency of the 10BROAD36 MAU in MHz/4; that
         is, in units of 250 kHz."
--     REFERENCE   
--         "[IEEE 802.3 Std], 30.5.1.1.9,
--          aBroadbandFrequencies.translationFrequency."
    ::= { broadMauBasicEntry 5 }

dot3MauType OBJECT IDENTIFIER
    ::= { snmpDot3MauMgt 4 }

dot3MauTypeAUI OBJECT IDENTIFIER
    ::= { dot3MauType 1 }

dot3MauType10Base5 OBJECT IDENTIFIER
    ::= { dot3MauType 2 }

dot3MauTypeFoirl OBJECT IDENTIFIER
    ::= { dot3MauType 3 }

dot3MauType10Base2 OBJECT IDENTIFIER
    ::= { dot3MauType 4 }

dot3MauType10BaseT OBJECT IDENTIFIER
    ::= { dot3MauType 5 }

dot3MauType10BaseFP OBJECT IDENTIFIER
    ::= { dot3MauType 6 }

dot3MauType10BaseFB OBJECT IDENTIFIER
    ::= { dot3MauType 7 }

dot3MauType10BaseFL OBJECT IDENTIFIER
    ::= { dot3MauType 8 }

dot3MauType10Broad36 OBJECT IDENTIFIER
    ::= { dot3MauType 9 }

dot3MauType10BaseTHD OBJECT IDENTIFIER
    ::= { dot3MauType 10 }

dot3MauType10BaseTFD OBJECT IDENTIFIER
    ::= { dot3MauType 11 }

dot3MauType10BaseFLHD OBJECT IDENTIFIER
    ::= { dot3MauType 12 }

dot3MauType10BaseFLFD OBJECT IDENTIFIER
    ::= { dot3MauType 13 }

dot3MauType100BaseT4 OBJECT IDENTIFIER
    ::= { dot3MauType 14 }

dot3MauType100BaseTXHD OBJECT IDENTIFIER
    ::= { dot3MauType 15 }

dot3MauType100BaseTXFD OBJECT IDENTIFIER
    ::= { dot3MauType 16 }

dot3MauType100BaseFXHD OBJECT IDENTIFIER
    ::= { dot3MauType 17 }

dot3MauType100BaseFXFD OBJECT IDENTIFIER
    ::= { dot3MauType 18 }

dot3MauType100BaseT2HD OBJECT IDENTIFIER
    ::= { dot3MauType 19 }

dot3MauType100BaseT2FD OBJECT IDENTIFIER
    ::= { dot3MauType 20 }

dot3MauType1000BaseXHD OBJECT IDENTIFIER
    ::= { dot3MauType 21 }

dot3MauType1000BaseXFD OBJECT IDENTIFIER
    ::= { dot3MauType 22 }

dot3MauType1000BaseLXHD OBJECT IDENTIFIER
    ::= { dot3MauType 23 }

dot3MauType1000BaseLXFD OBJECT IDENTIFIER
    ::= { dot3MauType 24 }

dot3MauType1000BaseSXHD OBJECT IDENTIFIER
    ::= { dot3MauType 25 }

dot3MauType1000BaseSXFD OBJECT IDENTIFIER
    ::= { dot3MauType 26 }

dot3MauType1000BaseCXHD OBJECT IDENTIFIER
    ::= { dot3MauType 27 }

dot3MauType1000BaseCXFD OBJECT IDENTIFIER
    ::= { dot3MauType 28 }

dot3MauType1000BaseTHD OBJECT IDENTIFIER
    ::= { dot3MauType 29 }

dot3MauType1000BaseTFD OBJECT IDENTIFIER
    ::= { dot3MauType 30 }

dot3IfMauAutoNegGroup OBJECT IDENTIFIER
    ::= { snmpDot3MauMgt 5 }

ifMauAutoNegTable OBJECT-TYPE
    SYNTAX      SEQUENCE OF IfMauAutoNegEntry
    ACCESS      not-accessible
    STATUS      mandatory
    DESCRIPTION 
        "Configuration and status objects for the
         auto-negotiation function of MAUs attached to
         interfaces."
    ::= { dot3IfMauAutoNegGroup 1 }

ifMauAutoNegEntry OBJECT-TYPE
    SYNTAX      IfMauAutoNegEntry
    ACCESS      not-accessible
    STATUS      mandatory
    DESCRIPTION 
        "An entry in the table, containing configuration
         and status information for the auto-negotiation
         function of a particular MAU."
    INDEX       { ifMauIfIndex, ifMauIndex }
    ::= { ifMauAutoNegTable 1 }

IfMauAutoNegEntry ::= SEQUENCE {
    ifMauAutoNegAdminStatus             INTEGER,
    ifMauAutoNegRemoteSignaling         INTEGER,
    ifMauAutoNegConfig                  INTEGER,
    ifMauAutoNegCapability              INTEGER,
    ifMauAutoNegCapAdvertised           INTEGER,
    ifMauAutoNegCapReceived             INTEGER,
    ifMauAutoNegRestart                 INTEGER,
    ifMauAutoNegCapabilityBits          OCTET STRING,
    ifMauAutoNegCapAdvertisedBits       OCTET STRING,
    ifMauAutoNegCapReceivedBits         OCTET STRING,
    ifMauAutoNegRemoteFaultAdvertised   INTEGER,
    ifMauAutoNegRemoteFaultReceived     INTEGER
}

ifMauAutoNegAdminStatus OBJECT-TYPE
    SYNTAX      INTEGER { enabled(1), disabled(2) }
    ACCESS      read-write
    STATUS      mandatory
    DESCRIPTION 
        "Setting this object to enabled(1) will cause
         the interface which has the auto-negotiation
         signaling ability to be enabled.
         
         If the value of this object is disabled(2) then
         the interface will act as it would if it had no
         auto-negotiation signaling.  Under these
         conditions, an IEEE 802.3 MAU will immediately
         be forced to the state indicated by the value of
         the object ifMauDefaultType.
         
         NOTE TO IMPLEMENTORS:  When
         ifMauAutoNegAdminStatus transitions from enabled
         to disabled, the agent implementation MUST
         ensure that the operational type of the MAU (as
         reported by ifMauType) correctly transitions to
         the value specified by the ifMauDefaultType
         object, rather than continuing to operate at the
         value earlier determined by the auto-negotiation
         function."
--     REFERENCE   
--         "[IEEE 802.3 Std], 30.6.1.1.2,
--          aAutoNegAdminState and 30.6.1.2.2,
--          acAutoNegAdminControl."
    ::= { ifMauAutoNegEntry 1 }

ifMauAutoNegRemoteSignaling OBJECT-TYPE
    SYNTAX      INTEGER { detected(1), notdetected(2) }
    ACCESS      read-only
    STATUS      mandatory
    DESCRIPTION 
        "A value indicating whether the remote end of
         the link is using auto-negotiation signaling. It
         takes the value detected(1) if and only if,
         during the previous link negotiation, FLP Bursts
         were received."
--     REFERENCE   
--         "[IEEE 802.3 Std], 30.6.1.1.3,
--          aAutoNegRemoteSignaling."
    ::= { ifMauAutoNegEntry 2 }

ifMauAutoNegConfig OBJECT-TYPE
    SYNTAX      INTEGER { other(1), configuring(2), complete(3), 
                    disabled(4), parallelDetectFail(5) }
    ACCESS      read-only
    STATUS      mandatory
    DESCRIPTION 
        "A value indicating the current status of the
         auto-negotiation process.  The enumeration
         parallelDetectFail(5) maps to a failure in
         parallel detection as defined in 28.2.3.1 of
         [IEEE 802.3 Std]."
--     REFERENCE   
--         "[IEEE 802.3 Std], 30.6.1.1.4,
--          aAutoNegAutoConfig."
    ::= { ifMauAutoNegEntry 4 }

ifMauAutoNegCapability OBJECT-TYPE
    SYNTAX      INTEGER
    ACCESS      read-only
    STATUS      deprecated
    DESCRIPTION 
        "********* THIS OBJECT IS DEPRECATED **********
         
         A value that uniquely identifies the set of
         capabilities of the local auto-negotiation
         entity.  The value is a sum which initially
         takes the value zero.  Then, for each capability
         of this interface, 2 raised to the power noted
         below is added to the sum. For example, an
         interface which has the capability to support
         only 100Base-TX half duplex would have a value
         of 32768 (2**15).  In contrast, an interface
         which supports both 100Base-TX half duplex and
         and 100Base-TX full duplex would have a value of
         98304 ((2**15) + (2**16)).
         
         The powers of 2 assigned to the capabilities are
         these:
         
         Power   Capability
           0       other or unknown
          (1-9)    (reserved)
          10       10BASE-T  half duplex mode
          11       10BASE-T  full duplex mode
          12       (reserved)
          13       (reserved)
          14       100BASE-T4
          15       100BASE-TX half duplex mode
          16       100BASE-TX full duplex mode
          17       (reserved)
          18       (reserved)
          19      100BASE-T2 half duplex mode
          20      100BASE-T2 full duplex mode
         
         Note that interfaces that support this MIB may
         have capabilities that extend beyond the scope
         of this MIB.
         This object has been deprecated in favour of
         ifMauAutoNegCapabilityBits"
--     REFERENCE   
--         "[IEEE 802.3 Std], 30.6.1.1.5,
--          aAutoNegLocalTechnologyAbility."
    ::= { ifMauAutoNegEntry 5 }

ifMauAutoNegCapAdvertised OBJECT-TYPE
    SYNTAX      INTEGER
    ACCESS      read-write
    STATUS      deprecated
    DESCRIPTION 
        "********* THIS OBJECT IS DEPRECATED **********
         
         A value that uniquely identifies the set of
         capabilities advertised by the local
         auto-negotiation entity. Refer to
         ifMauAutoNegCapability for a description of the
         possible values of this object.
         
         Capabilities in this object that are not
         available in ifMauAutoNegCapability cannot be
         enabled.
         
         This object has been deprecated in favour of
         ifMauAutoNegCapAdvertisedBits"
--     REFERENCE   
--         "[IEEE 802.3 Std], 30.6.1.1.6,
--          aAutoNegAdvertisedTechnologyAbility."
    ::= { ifMauAutoNegEntry 6 }

ifMauAutoNegCapReceived OBJECT-TYPE
    SYNTAX      INTEGER
    ACCESS      read-only
    STATUS      deprecated
    DESCRIPTION 
        "********* THIS OBJECT IS DEPRECATED **********
         
         A value that uniquely identifies the set of
         capabilities received from the remote
         auto-negotiation entity. Refer to
         ifMauAutoNegCapability for a description of the
         possible values of this object.
         
         Note that interfaces that support this MIB may
         be attached to remote auto-negotiation entities
         which have capabilities beyond the scope of this
         MIB.
         
         This object has been deprecated in favour of
         ifMauAutoNegCapReceivedBits"
--     REFERENCE   
--         "[IEEE 802.3 Std], 30.6.1.1.7,
--          aAutoNegReceivedTechnologyAbility."
    ::= { ifMauAutoNegEntry 7 }

ifMauAutoNegRestart OBJECT-TYPE
    SYNTAX      INTEGER { restart(1), norestart(2) }
    ACCESS      read-write
    STATUS      mandatory
    DESCRIPTION 
        "If the value of this object is set to
         restart(1) then this will force auto-negotiation
         to begin link renegotiation. If auto-negotiation
         signaling is disabled, a write to this object
         has no effect.
         
         Setting the value of this object to norestart(2)
         has no effect."
--     REFERENCE   
--         "[IEEE 802.3 Std], 30.6.1.2.1,
--          acAutoNegRestartAutoConfig."
    ::= { ifMauAutoNegEntry 8 }

ifMauAutoNegCapabilityBits OBJECT-TYPE
    SYNTAX      OCTET STRING
--                   { bOther(0), b10baseT(1), b10baseTFD(2), 
--                     b100baseT4(3), b100baseTX(4), b100baseTXFD(5), 
--                     b100baseT2(6), b100baseT2FD(7), bfdxPause(8), 
--                     bfdxAPause(9), bfdxSPause(10), bfdxBPause(11), 
--                     b1000baseX(12), b1000baseXFD(13), b1000baseT(14), 
--                     b1000baseTFD(15) }
    ACCESS      read-only
    STATUS      mandatory
    DESCRIPTION 
        "A value that uniquely identifies the set of
         capabilities of the local auto-negotiation
         entity.  Note that interfaces that support this
         MIB may have capabilities that extend beyond the
         scope of this MIB.
         
         Note that the local auto-negotiation entity may
         support some capabilities beyond the scope of
         this MIB.  This is indicated by returning the
         bit value bOther in addition to any bit values
         for capabilities that are listed above."
--     REFERENCE   
--         "[IEEE 802.3 Std], 30.6.1.1.5,
--          aAutoNegLocalTechnologyAbility."
    ::= { ifMauAutoNegEntry 9 }

ifMauAutoNegCapAdvertisedBits OBJECT-TYPE
    SYNTAX      OCTET STRING
--                   { bOther(0), b10baseT(1), b10baseTFD(2), 
--                     b100baseT4(3), b100baseTX(4), b100baseTXFD(5), 
--                     b100baseT2(6), b100baseT2FD(7), bFdxPause(8), 
--                     bFdxAPause(9), bFdxSPause(10), bFdxBPause(11), 
--                     b1000baseX(12), b1000baseXFD(13), b1000baseT(14), 
--                     b1000baseTFD(15) }
    ACCESS      read-write
    STATUS      mandatory
    DESCRIPTION 
        "A value that uniquely identifies the set of
         capabilities advertised by the local
         auto-negotiation entity.
         
         Capabilities in this object that are not
         available in ifMauAutoNegCapabilityBits cannot
         be enabled.
         Note that the local auto-negotiation entity may
         advertise some capabilities beyond the scope of
         this MIB.  This is indicated by returning the
         bit value bOther in addition to any bit values
         for capabilities that are listed above."
--     REFERENCE   
--         "[IEEE 802.3 Std], 30.6.1.1.6,
--          aAutoNegAdvertisedTechnologyAbility."
    ::= { ifMauAutoNegEntry 10 }

ifMauAutoNegCapReceivedBits OBJECT-TYPE
    SYNTAX      OCTET STRING
--                   { bOther(0), b10baseT(1), b10baseTFD(2), 
--                     b100baseT4(3), b100baseTX(4), b100baseTXFD(5), 
--                     b100baseT2(6), b100baseT2FD(7), bFdxPause(8), 
--                     bFdxAPause(9), bFdxSPause(10), bFdxBPause(11), 
--                     b1000baseX(12), b1000baseXFD(13), b1000baseT(14), 
--                     b1000baseTFD(15) }
    ACCESS      read-only
    STATUS      mandatory
    DESCRIPTION 
        "A value that uniquely identifies the set of
         capabilities received from the remote
         auto-negotiation entity.
         
         Note that interfaces that support this MIB may
         be attached to remote auto-negotiation entities
         which have capabilities beyond the scope of this
         MIB.  This is indicated by returning the bit
         value bOther in addition to any bit values for
         capabilities that are listed above."
--     REFERENCE   
--         "[IEEE 802.3 Std], 30.6.1.1.7,
--          aAutoNegReceivedTechnologyAbility."
    ::= { ifMauAutoNegEntry 11 }

ifMauAutoNegRemoteFaultAdvertised OBJECT-TYPE
    SYNTAX      INTEGER { noError(1), offline(2), linkFailure(3), 
                    autoNegError(4) }
    ACCESS      read-write
    STATUS      mandatory
    DESCRIPTION 
        "A value that identifies any local fault
         indications that this MAU has detected and will
         advertise at the next auto-negotiation
         interaction for 1000Mbps MAUs."
--     REFERENCE   
--         "[IEEE 802.3 Std], 30.6.1.1.6,
--          aAutoNegAdvertisedTechnologyAbility."
    ::= { ifMauAutoNegEntry 12 }

ifMauAutoNegRemoteFaultReceived OBJECT-TYPE
    SYNTAX      INTEGER { noError(1), offline(2), linkFailure(3), 
                    autoNegError(4) }
    ACCESS      read-only
    STATUS      mandatory
    DESCRIPTION 
        "A value that identifies any fault indications
         received from the far end of a link by the
         local auto-negotiation entity for 1000Mbps
         MAUs."
--     REFERENCE   
--         "[IEEE 802.3 Std], 30.6.1.1.7,
--          aAutoNegReceivedTechnologyAbility."
    ::= { ifMauAutoNegEntry 13 }

mauModConf OBJECT IDENTIFIER
    ::= { mauMod 1 }

mauModCompls OBJECT IDENTIFIER
    ::= { mauModConf 1 }

mauModObjGrps OBJECT IDENTIFIER
    ::= { mauModConf 2 }

mauModNotGrps OBJECT IDENTIFIER
    ::= { mauModConf 3 }

rpMauJabberTrap TRAP-TYPE
    ENTERPRISE  snmpDot3MauMgt
    VARIABLES   { rpMauJabberState }
--     STATUS      mandatory
    DESCRIPTION 
        "This trap is sent whenever a managed repeater
         MAU enters the jabber state.
         
         The agent MUST throttle the generation of
         consecutive rpMauJabberTraps so that there is at
         least a five-second gap between them."
--     REFERENCE   
--         "[IEEE 802.3 Mgt], 30.5.1.3.1, nJabber
--          notification."
    ::= 1

ifMauJabberTrap TRAP-TYPE
    ENTERPRISE  snmpDot3MauMgt
    VARIABLES   { ifMauJabberState }
--     STATUS      mandatory
    DESCRIPTION 
        "This trap is sent whenever a managed interface
         MAU enters the jabber state.
         
         The agent MUST throttle the generation of
         consecutive ifMauJabberTraps so that there is at
         least a five-second gap between them."
--     REFERENCE   
--         "[IEEE 802.3 Mgt], 30.5.1.3.1, nJabber
--          notification."
    ::= 2

mauRpGrpBasic OBJECT IDENTIFIER
    ::= { mauModObjGrps 1 }

-- mauRpGrpBasic OBJECT-GROUP
--     OBJECTS     { rpMauGroupIndex, rpMauPortIndex, rpMauIndex, 
--                   rpMauType, rpMauStatus, rpMauMediaAvailable, 
--                   rpMauMediaAvailableStateExits, rpMauJabberState, 
--                   rpMauJabberingStateEnters }
--     STATUS      mandatory
--     DESCRIPTION 
--         "Basic conformance group for MAUs attached to
--          repeater ports.  This group is also the
--          conformance specification for RFC 1515
--          implementations."
--     ::= { mauModObjGrps 1 }

mauRpGrp100Mbs OBJECT IDENTIFIER
    ::= { mauModObjGrps 2 }

-- mauRpGrp100Mbs OBJECT-GROUP
--     OBJECTS     { rpMauFalseCarriers }
--     STATUS      mandatory
--     DESCRIPTION 
--         "Conformance group for MAUs attached to
--          repeater ports with 100 Mb/s or greater
--          capability."
--     ::= { mauModObjGrps 2 }

mauRpGrpJack OBJECT IDENTIFIER
    ::= { mauModObjGrps 3 }

-- mauRpGrpJack OBJECT-GROUP
--     OBJECTS     { rpJackType }
--     STATUS      mandatory
--     DESCRIPTION 
--         "Conformance group for MAUs attached to
--          repeater ports with managed jacks."
--     ::= { mauModObjGrps 3 }

mauIfGrpBasic OBJECT IDENTIFIER
    ::= { mauModObjGrps 4 }

-- mauIfGrpBasic OBJECT-GROUP
--     OBJECTS     { ifMauIfIndex, ifMauIndex, ifMauType, ifMauStatus, 
--                   ifMauMediaAvailable, ifMauMediaAvailableStateExits, 
--                   ifMauJabberState, ifMauJabberingStateEnters }
--     STATUS      mandatory
--     DESCRIPTION 
--         "Basic conformance group for MAUs attached to
--          interfaces.  This group also provides a
--          conformance specification for RFC 1515
--          implementations."
--     ::= { mauModObjGrps 4 }

mauIfGrp100Mbs OBJECT IDENTIFIER
    ::= { mauModObjGrps 5 }

-- mauIfGrp100Mbs OBJECT-GROUP
--     OBJECTS     { ifMauFalseCarriers, ifMauTypeList, ifMauDefaultType, 
--                   ifMauAutoNegSupported }
--     STATUS      deprecated
--     DESCRIPTION 
--         "********* THIS GROUP IS DEPRECATED **********
--          
--          Conformance group for MAUs attached to
--          interfaces with 100 Mb/s capability.
--          
--          This object group has been deprecated in favor
--          of mauIfGrpHighCapacity."
--     ::= { mauModObjGrps 5 }

mauIfGrpJack OBJECT IDENTIFIER
    ::= { mauModObjGrps 6 }

-- mauIfGrpJack OBJECT-GROUP
--     OBJECTS     { ifJackType }
--     STATUS      mandatory
--     DESCRIPTION 
--         "Conformance group for MAUs attached to
--          interfaces with managed jacks."
--     ::= { mauModObjGrps 6 }

mauIfGrpAutoNeg OBJECT IDENTIFIER
    ::= { mauModObjGrps 7 }

-- mauIfGrpAutoNeg OBJECT-GROUP
--     OBJECTS     { ifMauAutoNegAdminStatus, 
--                   ifMauAutoNegRemoteSignaling, ifMauAutoNegConfig, 
--                   ifMauAutoNegCapability, ifMauAutoNegCapAdvertised, 
--                   ifMauAutoNegCapReceived, ifMauAutoNegRestart }
--     STATUS      deprecated
--     DESCRIPTION 
--         "********* THIS GROUP IS DEPRECATED **********
--          
--          Conformance group for MAUs attached to
--          interfaces with managed auto-negotiation.
--          
--          This object group has been deprecated in favor
--          of mauIfGrpAutoNeg2."
--     ::= { mauModObjGrps 7 }

mauBroadBasic OBJECT IDENTIFIER
    ::= { mauModObjGrps 8 }

-- mauBroadBasic OBJECT-GROUP
--     OBJECTS     { broadMauIfIndex, broadMauIndex, 
--                   broadMauXmtRcvSplitType, broadMauXmtCarrierFreq, 
--                   broadMauTranslationFreq }
--     STATUS      deprecated
--     DESCRIPTION 
--         "********* THIS GROUP IS DEPRECATED **********
--          
--          Conformance group for broadband MAUs attached
--          to interfaces.
--          
--          This object group is deprecated.  There have
--          been no reported implementations of this group,
--          and it was felt to be unlikely that there will
--          be any future implementations."
--     ::= { mauModObjGrps 8 }

mauIfGrpHighCapacity OBJECT IDENTIFIER
    ::= { mauModObjGrps 9 }

-- mauIfGrpHighCapacity OBJECT-GROUP
--     OBJECTS     { ifMauFalseCarriers, ifMauTypeListBits, 
--                   ifMauDefaultType, ifMauAutoNegSupported }
--     STATUS      mandatory
--     DESCRIPTION 
--         "Conformance group for MAUs attached to
--          interfaces with 100 Mb/s or greater capability."
--     ::= { mauModObjGrps 9 }

mauIfGrpAutoNeg2 OBJECT IDENTIFIER
    ::= { mauModObjGrps 10 }

-- mauIfGrpAutoNeg2 OBJECT-GROUP
--     OBJECTS     { ifMauAutoNegAdminStatus, 
--                   ifMauAutoNegRemoteSignaling, ifMauAutoNegConfig, 
--                   ifMauAutoNegCapabilityBits, 
--                   ifMauAutoNegCapAdvertisedBits, 
--                   ifMauAutoNegCapReceivedBits, ifMauAutoNegRestart }
--     STATUS      mandatory
--     DESCRIPTION 
--         "Conformance group for MAUs attached to
--          interfaces with managed auto-negotiation."
--     ::= { mauModObjGrps 10 }

mauIfGrpAutoNeg1000Mbps OBJECT IDENTIFIER
    ::= { mauModObjGrps 11 }

-- mauIfGrpAutoNeg1000Mbps OBJECT-GROUP
--     OBJECTS     { ifMauAutoNegRemoteFaultAdvertised, 
--                   ifMauAutoNegRemoteFaultReceived }
--     STATUS      mandatory
--     DESCRIPTION 
--         "Conformance group for 1000Mbps MAUs attached to
--          interfaces with managed auto-negotiation."
--     ::= { mauModObjGrps 11 }

rpMauNotifications OBJECT IDENTIFIER
    ::= { mauModNotGrps 1 }

-- rpMauNotifications NOTIFICATION-GROUP
--     NOTIFICATIONS { rpMauJabberTrap }
--     STATUS      mandatory
--     DESCRIPTION 
--         "Notifications for repeater MAUs."
--     ::= { mauModNotGrps 1 }

ifMauNotifications OBJECT IDENTIFIER
    ::= { mauModNotGrps 2 }

-- ifMauNotifications NOTIFICATION-GROUP
--     NOTIFICATIONS { ifMauJabberTrap }
--     STATUS      mandatory
--     DESCRIPTION 
--         "Notifications for interface MAUs."
--     ::= { mauModNotGrps 2 }

mauModRpCompl OBJECT IDENTIFIER
    ::= { mauModCompls 1 }

-- mauModRpCompl MODULE-COMPLIANCE
--     STATUS      deprecated
--     DESCRIPTION 
--         "******** THIS COMPLIANCE IS DEPRECATED ********
--          
--          Compliance for MAUs attached to repeater
--          ports.
--          This compliance is deprecated and replaced by
--          mauModRpCompl2, which corrects an oversight by
--          allowing rpMauStatus to be implemented
--          read-only."

--     MODULE      -- -- this module

--         MANDATORY-GROUPS        { mauRpGrpBasic }

--         GROUP   mauRpGrp100Mbs
--         DESCRIPTION   
--         "Implementation of this optional group is
--          recommended for MAUs which have 100Mb/s or
--          greater capability."

--         GROUP   mauRpGrpJack
--         DESCRIPTION   
--         "Implementation of this optional group is
--          recommended for MAUs which have one or more
--          external jacks."

--         GROUP   rpMauNotifications
--         DESCRIPTION   
--         "Implementation of this group is recommended
--          for MAUs attached to repeater ports."

--     ::= { mauModCompls 1 }

mauModIfCompl OBJECT IDENTIFIER
    ::= { mauModCompls 2 }

-- mauModIfCompl MODULE-COMPLIANCE
--     STATUS      deprecated
--     DESCRIPTION 
--         "******** THIS COMPLIANCE IS DEPRECATED ********
--          
--          Compliance for MAUs attached to interfaces.
--          
--          This compliance is deprecated and replaced by
--          mauModIfCompl2."

--     MODULE      -- -- this module

--         MANDATORY-GROUPS        { mauIfGrpBasic }

--         GROUP   mauIfGrp100Mbs
--         DESCRIPTION   
--         "Implementation of this optional group is
--          recommended for MAUs which have 100Mb/s
--          capability."

--         GROUP   mauIfGrpJack
--         DESCRIPTION   
--         "Implementation of this optional group is
--          recommended for MAUs which have one or more
--          external jacks."

--         GROUP   mauIfGrpAutoNeg
--         DESCRIPTION   
--         "Implementation of this group is mandatory
--          for MAUs which support managed
--          auto-negotiation."

--         GROUP   mauBroadBasic
--         DESCRIPTION   
--         "Implementation of this group is mandatory
--          for broadband MAUs."

--         GROUP   ifMauNotifications
--         DESCRIPTION   
--         "Implementation of this group is recommended
--          for MAUs attached to interfaces."

--     ::= { mauModCompls 2 }

mauModIfCompl2 OBJECT IDENTIFIER
    ::= { mauModCompls 3 }

-- mauModIfCompl2 MODULE-COMPLIANCE
--     STATUS      mandatory
--     DESCRIPTION 
--         "Compliance for MAUs attached to interfaces."

--     MODULE      -- -- this module

--         MANDATORY-GROUPS        { mauIfGrpBasic }

--         GROUP   mauIfGrpHighCapacity
--         DESCRIPTION   
--         "Implementation of this optional group is
--          recommended for MAUs which have 100Mb/s
--          or greater capability."

--         GROUP   mauIfGrpJack
--         DESCRIPTION   
--         "Implementation of this optional group is
--          recommended for MAUs which have one or more
--          external jacks."

--         GROUP   mauIfGrpAutoNeg2
--         DESCRIPTION   
--         "Implementation of this group is mandatory
--          for MAUs which support managed
--          auto-negotiation."

--         GROUP   mauIfGrpAutoNeg1000Mbps
--         DESCRIPTION   
--         "Implementation of this group is mandatory
--          for MAUs which have 1000Mb/s or greater
--          capability and support managed
--          auto-negotiation."

--         GROUP   ifMauNotifications
--         DESCRIPTION   
--         "Implementation of this group is recommended
--          for MAUs attached to interfaces."

--         OBJECT  ifMauStatus
--         MIN-ACCESS  read-only
--         DESCRIPTION   
--         "Write access is not required."

--     ::= { mauModCompls 3 }

mauModRpCompl2 OBJECT IDENTIFIER
    ::= { mauModCompls 4 }

-- mauModRpCompl2 MODULE-COMPLIANCE
--     STATUS      mandatory
--     DESCRIPTION 
--         "Compliance for MAUs attached to repeater
--          ports."

--     MODULE      -- -- this module

--         MANDATORY-GROUPS        { mauRpGrpBasic }

--         GROUP   mauRpGrp100Mbs
--         DESCRIPTION   
--         "Implementation of this optional group is
--          recommended for MAUs which have 100Mb/s or
--          greater capability."

--         GROUP   mauRpGrpJack
--         DESCRIPTION   
--         "Implementation of this optional group is
--          recommended for MAUs which have one or more
--          external jacks."

--         GROUP   rpMauNotifications
--         DESCRIPTION   
--         "Implementation of this group is recommended
--          for MAUs attached to repeater ports."

--         OBJECT  rpMauStatus
--         MIN-ACCESS  read-only
--         DESCRIPTION   
--         "Write access is not required."

--     ::= { mauModCompls 4 }

END -- end of module MAU-MIB.
