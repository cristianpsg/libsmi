A DEFINITIONS ::= BEGIN

a OBJECT IDENTIFIER ::= { iso 1 }

x1 OBJECT IDENTIFIER ::= { b1 1 }
x2 OBJECT IDENTIFIER ::= { b2 1 }
x3 OBJECT IDENTIFIER ::= { b3 1 }

b2 OBJECT IDENTIFIER ::= { a 2 }
b3 OBJECT IDENTIFIER ::= { a 3 }
b1 OBJECT IDENTIFIER ::= { a 1 }

END
