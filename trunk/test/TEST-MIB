-- file: a21.mi2
-- The following errors will be generated when this file
-- is compiled!
-- W: f(a21.mi2), (102,1) Item "a1Col" is not contained in any group defined in the current module
-- W: f(a21.mi2), (211,1) Item "aO13" is not contained in any group defined in the current module
-- W: f(a21.mi2), (220,1) Item "aO14" is not contained in any group defined in the current module
-- W: f(a21.mi2), (228,1) Item "aO15" is not contained in any group defined in the current module
-- W: f(a21.mi2), (236,1) Item "aO16" is not contained in any group defined in the current module
-- W: f(a21.mi2), (265,21) Item "aOgroup2" in module-compliance "aCompl1" has incompatable status
-- E: f(a21.mi2), (268,16) MIN-ACCESS incompatable with that for "aO1"
-- E: f(a21.mi2), (275,45) Subtype size/range is not compatable with base size/range
-- E: f(a21.mi2), (275,25) For "aO2", syntax is not a proper refinement
-- E: f(a21.mi2), (276,25) Syntax type does not match that for "aO2"
-- E: f(a21.mi2), (288,25) For "aO13", syntax is not a proper refinement
-- E: f(a21.mi2), (280,16) OBJECT-TYPE "aO14" is not in a MANDATORY or conditional group for module "A"
-- E: f(a21.mi2), (286,16) OBJECT-TYPE "aO13" is not in a MANDATORY or conditional group for module "A"
-- E: f(a21.mi2), (308,29) ACCESS incompatable with that for "snmpStatsEncodingErrors"


A
DEFINITIONS ::= BEGIN
    IMPORTS
        MODULE-IDENTITY, OBJECT-TYPE, OBJECT-IDENTITY,
	NOTIFICATION-TYPE, experimental,
        Integer32, IpAddress, Counter32, Gauge32,
        TimeTicks, Opaque, NsapAddress, Counter64,
        UInteger32
                FROM SNMPv2-SMI
	TEXTUAL-CONVENTION, DisplayString
		FROM SNMPv2-TC
        OBJECT-GROUP, MODULE-COMPLIANCE, AGENT-CAPABILITIES
                FROM SNMPv2-CONF;


aMi MODULE-IDENTITY
        LAST-UPDATED "9403240002Z"
        ORGANIZATION "MIBs R Us"
        CONTACT-INFO
            "Fred Flintstone

             201 Bedrock Lane
             Granite City, CA  95051
             US
             Tel: +1 508 555 1212
             E-mail: fred@mibrus.com"
        DESCRIPTION
            "An Example Module Identity"
        ::= { experimental 11999 0 }


ATC1 ::= TEXTUAL-CONVENTION 
	STATUS current
	DESCRIPTION "ATC1"
	SYNTAX INTEGER(1..100 | 200 | 300..MAX)


a OBJECT IDENTIFIER ::= { experimental 11999 }

aI1 OBJECT-IDENTITY
	STATUS current
	DESCRIPTION "aI1"
	::= { a 1000 }


aN1 NOTIFICATION-TYPE
	OBJECTS { aO1, aO2 }
	STATUS current
	DESCRIPTION "aN1"
	::= { a 1001 }


a1Table OBJECT-TYPE
        SYNTAX      SEQUENCE OF A1Entry
        MAX-ACCESS  not-accessible
        STATUS      current
        DESCRIPTION
                "a1Table"
        ::= { a 1 }

a1Entry OBJECT-TYPE
        SYNTAX      A1Entry
        MAX-ACCESS  not-accessible
        STATUS      current
        DESCRIPTION
                "a1Entry"
        INDEX { a1Index }
        ::= { a1Table 1 }

A1Entry ::= SEQUENCE {
        a1Index UInteger32,
        a1Col Integer32
        }

a1Index OBJECT-TYPE
        SYNTAX      UInteger32
        MAX-ACCESS  not-accessible
        STATUS      current
        DESCRIPTION
                "a1Index"
        ::= { a1Entry 1 }

a1Col OBJECT-TYPE
        SYNTAX      Integer32
        MAX-ACCESS  read-create
        STATUS      current
        DESCRIPTION
                "a1Col"
        ::= { a1Entry 2 }

aO OBJECT IDENTIFIER ::= { a 2 }

aO1 OBJECT-TYPE
        SYNTAX      Integer32
        MAX-ACCESS  read-only
        STATUS      current
        DESCRIPTION
                "aO1"
        ::= { aO 1 }

aO2 OBJECT-TYPE
        SYNTAX      OCTET STRING (SIZE (0..100))
        MAX-ACCESS  read-only
        STATUS      current
        DESCRIPTION
                "aO2"
        ::= { aO 2 }

aO3 OBJECT-TYPE
        SYNTAX      OBJECT IDENTIFIER
        MAX-ACCESS  read-only
        STATUS      current
        DESCRIPTION
                "aO3"
        ::= { aO 3 }

aO4 OBJECT-TYPE
        SYNTAX      BIT STRING {
                        zero(0), two(2), three(3), one(1) }
        MAX-ACCESS  read-write
        STATUS      current
        DESCRIPTION
                "aO4"
        ::= { aO 4 }

aO5 OBJECT-TYPE
        SYNTAX      IpAddress
        MAX-ACCESS  read-only
        STATUS      current
        DESCRIPTION
                "aO5"
        ::= { aO 5 }

aO6 OBJECT-TYPE
        SYNTAX      Counter32
        MAX-ACCESS  read-only
        STATUS      current
        DESCRIPTION
                "aO6"
        ::= { aO 6 }

aO7 OBJECT-TYPE
        SYNTAX      Gauge32
        MAX-ACCESS  read-only
        STATUS      current
        DESCRIPTION
                "aO7"
        ::= { aO 7 }


aO8 OBJECT-TYPE
        SYNTAX      TimeTicks
        MAX-ACCESS  read-only
        STATUS      current
        DESCRIPTION
                "aO8"
        ::= { aO 8 }


aO9 OBJECT-TYPE
        SYNTAX      Opaque
        MAX-ACCESS  read-only
        STATUS      current
        DESCRIPTION
                "aO9"
        ::= { aO 9 }

aO10 OBJECT-TYPE
        SYNTAX      NsapAddress
        MAX-ACCESS  read-only
        STATUS      current
        DESCRIPTION
                "aO10"
        ::= { aO 10 }

aO11 OBJECT-TYPE
        SYNTAX      Counter64
        MAX-ACCESS  read-only
        STATUS      current
        DESCRIPTION
                "aO11"
        ::= { aO 11 }

aO12 OBJECT-TYPE
        SYNTAX      UInteger32
        MAX-ACCESS  read-only
        STATUS      obsolete
        DESCRIPTION
                "aO12"
        ::= { aO 12 }

aO13 OBJECT-TYPE
        SYNTAX      INTEGER {
                        zero(0), ten(10), thirty(30), twenty(20) }
        MAX-ACCESS  read-only
        STATUS      current
        DESCRIPTION
                "aO13"
        ::= { aO 13 }

aO14 OBJECT-TYPE
        SYNTAX      OCTET STRING (SIZE (0..50))
        MAX-ACCESS  read-only
        STATUS      current
        DESCRIPTION
                "aO14"
        ::= { aO 14 }

aO15 OBJECT-TYPE
        SYNTAX      ATC1 (MIN..10 | 500..MAX)
        MAX-ACCESS  read-only
        STATUS      current
        DESCRIPTION
                "aO15"
        ::= { aO 15 }

aO16 OBJECT-TYPE
        SYNTAX      DisplayString (SIZE(15..MAX))
        MAX-ACCESS  read-only
        STATUS      current
        DESCRIPTION
                "aO16"
        ::= { aO 16 }

aOgroup1 OBJECT-GROUP
        OBJECTS {
            aO1, aO2, aO3, aO4, aO5, aO6, aO7, aO8, aO9, aO10, aO11 }
        STATUS      current
        DESCRIPTION
            "aOgroup"
        ::= { aO 0 1 }

aOgroup2 OBJECT-GROUP
        OBJECTS { aO12 }
        STATUS      obsolete
        DESCRIPTION
            "aOgroup"
        ::= { aO 0 2 }

aCompl1 MODULE-COMPLIANCE
        STATUS      current
        DESCRIPTION
            "aCompl1"
        MODULE
            MANDATORY-GROUPS { aOgroup1 }
        GROUP       aOgroup2
        DESCRIPTION
            "aOgroup2 in aCompl1"
        OBJECT aO1
        SYNTAX          Integer32 (1..23)
        WRITE-SYNTAX    Integer32 (30..100)
        MIN-ACCESS      read-write
        DESCRIPTION
            "aO1 in aCompl1"
        OBJECT aO2
        SYNTAX          OCTET STRING (SIZE (90..110))
        WRITE-SYNTAX    Integer32
        MIN-ACCESS      not-accessible
        DESCRIPTION
            "aO2 in aCompl1"
        OBJECT aO14
        SYNTAX          OCTET STRING (SIZE (1..10))
        WRITE-SYNTAX    OCTET STRING (SIZE (10..20))
        MIN-ACCESS      not-accessible
        DESCRIPTION
            "aO14 in aCompl1"
        OBJECT aO13
        SYNTAX          INTEGER { ten(10) }
        WRITE-SYNTAX    INTEGER { zero(1) }
        MIN-ACCESS      not-accessible
        DESCRIPTION
            "aO14 in aCompl1"

        ::= { aMi 1 }        

aAC1 AGENT-CAPABILITIES
       PRODUCT-RELEASE      "Barney Agent"
       STATUS               current
       DESCRIPTION          "Barney agent for MIBs R Us"
       REFERENCE            "SMIC Test Agent Caps"

       SUPPORTS             RFC1213-MIB
           INCLUDES         { system, at, ip, icmp, tcp, udp }

       SUPPORTS             SNMPv2-MIB
           INCLUDES         { snmpStatsGroup, snmpV1Group,
                              snmpORGroup, snmpTrapGroup, snmpSetGroup }

           VARIATION        snmpStatsEncodingErrors
               ACCESS       not-accessible
               DESCRIPTION  "Not available for retrieval currently"

           VARIATION        snmpSetSerialNo
               SYNTAX       INTEGER (0..255)
               WRITE-SYNTAX INTEGER (50..60)
               DESCRIPTION  "Limited size of TestAndIncr implementation"
 
           VARIATION        snmpV2EnableAuthenTraps
               ACCESS       read-only
               DESCRIPTION  "Limit access to the snmpV2EnableAuthenTraps object"

	::= { a 1002 }


END
