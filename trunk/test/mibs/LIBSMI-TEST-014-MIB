LIBSMI-TEST-014-MIB DEFINITIONS ::= BEGIN

IMPORTS
    MODULE-IDENTITY, OBJECT-TYPE, Integer32
	FROM SNMPv2-SMI
    MacAddress
	FROM SNMPv2-TC
    OBJECT-GROUP
	FROM SNMPv2-CONF
    testMib
        FROM LIBSMI-TEST-MIB;

libsmiTest014Mib MODULE-IDENTITY
    LAST-UPDATED    "200109270000Z"
    ORGANIZATION    
            "TU Braunschweig"
    CONTACT-INFO    
            "        Frank Strauss
             
             Postal: TU Braunschweig
                     Muehlenpfordtstrasse 23
                     38106 Braunschweig
                     Germany
             
              Phone: +49 531 391-3283
              EMail: strauss@ibr.cs.tu-bs.de
               http://www.ibr.cs.tu-bs.de/~strauss/"
    DESCRIPTION     
            "This MIB module contains one or more intentional errors,
             and/or unusual contents. Its only purpose is to check
             the abilities of MIB parsers to detect these circumstances.
             
             This MIB module is orginally written in SMIv2 format.
             
             This module checks for range normalization, thus there are
	     no errors expected for this module. However the parser might
	     complain about ranges not being in ascending order.

	     The libsmi parser is expected to report:
LIBSMI-TEST-014-MIB:102: warning: index of row `barEntry' can exceed OID size limit by 1 subidentifier(s)
LIBSMI-TEST-014-MIB:186: warning: index of row `barImpliedEntry' can exceed OID size limit by 1 subidentifier(s)
LIBSMI-TEST-014-MIB:251: index element `fooStringName' of row `fooStringEntry' must have a size restriction
LIBSMI-TEST-014-MIB:230: warning: index of row `fooStringEntry' can exceed OID size limit by 65427 subidentifier(s)
LIBSMI-TEST-014-MIB:294: warning: index element `fooOidName' of row `fooOidEntry' should but cannot have a size restriction
LIBSMI-TEST-014-MIB:273: warning: index of row `fooOidEntry' can exceed OID size limit by 20 subidentifier(s)
LIBSMI-TEST-014-MIB:309: warning: current group `fooOidBarGroup' is not referenced in this module
	    "
    REVISION        "200109270000Z"
    DESCRIPTION     
            "Initial Revision."
    ::= { testMib 14 }

fooTable OBJECT-TYPE
    SYNTAX	SEQUENCE OF FooEntry
    MAX-ACCESS	not-accessible
    STATUS	current
    DESCRIPTION	"..."
    ::= { libsmiTest014Mib 1 }

fooEntry OBJECT-TYPE
    SYNTAX	FooEntry
    MAX-ACCESS	not-accessible
    STATUS	current
    DESCRIPTION "..."
    INDEX	{ fooAddr, fooName }
    ::= { fooTable 1 }

FooEntry ::= SEQUENCE {
    fooAddr	MacAddress,
    fooName	OCTET STRING,
    fooData	Integer32
}

fooAddr OBJECT-TYPE
    SYNTAX	MacAddress
    MAX-ACCESS  not-accessible
    STATUS	current
    DESCRIPTION	"..."
    ::= { fooEntry 1 }

fooName OBJECT-TYPE
    SYNTAX	OCTET STRING (SIZE(0..108))
    MAX-ACCESS  not-accessible
    STATUS	current
    DESCRIPTION "..."
    ::= { fooEntry 2 }

fooData OBJECT-TYPE
    SYNTAX	Integer32
    MAX-ACCESS  read-only
    STATUS	current
    DESCRIPTION "..."
    ::= { fooEntry 3 }

barTable OBJECT-TYPE
    SYNTAX	SEQUENCE OF BarEntry
    MAX-ACCESS	not-accessible
    STATUS	current
    DESCRIPTION	"..."
    ::= { libsmiTest014Mib 2 }

barEntry OBJECT-TYPE
    SYNTAX	BarEntry
    MAX-ACCESS	not-accessible
    STATUS	current
    DESCRIPTION "..."
    INDEX	{ barAddr, barName }
    ::= { barTable 1 }

BarEntry ::= SEQUENCE {
    barAddr	MacAddress,
    barName	OCTET STRING,
    barData	Integer32
}

barAddr OBJECT-TYPE
    SYNTAX	MacAddress
    MAX-ACCESS  not-accessible
    STATUS	current
    DESCRIPTION	"..."
    ::= { barEntry 1 }

barName OBJECT-TYPE
    SYNTAX	OCTET STRING (SIZE(0..109))
    MAX-ACCESS  not-accessible
    STATUS	current
    DESCRIPTION "..."
    ::= { barEntry 2 }

barData OBJECT-TYPE
    SYNTAX	Integer32
    MAX-ACCESS  read-only
    STATUS	current
    DESCRIPTION "..."
    ::= { barEntry 3 }

fooImpliedTable OBJECT-TYPE
    SYNTAX	SEQUENCE OF FooImpliedEntry
    MAX-ACCESS	not-accessible
    STATUS	current
    DESCRIPTION	"..."
    ::= { libsmiTest014Mib 3 }

fooImpliedEntry OBJECT-TYPE
    SYNTAX	FooImpliedEntry
    MAX-ACCESS	not-accessible
    STATUS	current
    DESCRIPTION "..."
    INDEX	{ fooImpliedAddr, IMPLIED fooImpliedName }
    ::= { fooImpliedTable 1 }

FooImpliedEntry ::= SEQUENCE {
    fooImpliedAddr	MacAddress,
    fooImpliedName	OCTET STRING,
    fooImpliedData	Integer32
}

fooImpliedAddr OBJECT-TYPE
    SYNTAX	MacAddress
    MAX-ACCESS  not-accessible
    STATUS	current
    DESCRIPTION	"..."
    ::= { fooImpliedEntry 1 }

fooImpliedName OBJECT-TYPE
    SYNTAX	OCTET STRING (SIZE(0..109))
    MAX-ACCESS  not-accessible
    STATUS	current
    DESCRIPTION "..."
    ::= { fooImpliedEntry 2 }

fooImpliedData OBJECT-TYPE
    SYNTAX	Integer32
    MAX-ACCESS  read-only
    STATUS	current
    DESCRIPTION "..."
    ::= { fooImpliedEntry 3 }

barImpliedTable OBJECT-TYPE
    SYNTAX	SEQUENCE OF BarImpliedEntry
    MAX-ACCESS	not-accessible
    STATUS	current
    DESCRIPTION	"..."
    ::= { libsmiTest014Mib 4 }

barImpliedEntry OBJECT-TYPE
    SYNTAX	BarImpliedEntry
    MAX-ACCESS	not-accessible
    STATUS	current
    DESCRIPTION "..."
    INDEX	{ barImpliedAddr, IMPLIED barImpliedName }
    ::= { barImpliedTable 1 }

BarImpliedEntry ::= SEQUENCE {
    barImpliedAddr	MacAddress,
    barImpliedName	OCTET STRING,
    barImpliedData	Integer32
}

barImpliedAddr OBJECT-TYPE
    SYNTAX	MacAddress
    MAX-ACCESS  not-accessible
    STATUS	current
    DESCRIPTION	"..."
    ::= { barImpliedEntry 1 }

barImpliedName OBJECT-TYPE
    SYNTAX	OCTET STRING (SIZE(0..110))
    MAX-ACCESS  not-accessible
    STATUS	current
    DESCRIPTION "..."
    ::= { barImpliedEntry 2 }

barImpliedData OBJECT-TYPE
    SYNTAX	Integer32
    MAX-ACCESS  read-only
    STATUS	current
    DESCRIPTION "..."
    ::= { barImpliedEntry 3 }



fooStringTable OBJECT-TYPE
    SYNTAX	SEQUENCE OF FooStringEntry
    MAX-ACCESS	not-accessible
    STATUS	current
    DESCRIPTION	"..."
    ::= { libsmiTest014Mib 5 }

fooStringEntry OBJECT-TYPE
    SYNTAX	FooStringEntry
    MAX-ACCESS	not-accessible
    STATUS	current
    DESCRIPTION "..."
    INDEX	{ fooStringAddr, fooStringName }
    ::= { fooStringTable 1 }

FooStringEntry ::= SEQUENCE {
    fooStringAddr	MacAddress,
    fooStringName	OCTET STRING,
    fooStringData	Integer32
}

fooStringAddr OBJECT-TYPE
    SYNTAX	MacAddress
    MAX-ACCESS  not-accessible
    STATUS	current
    DESCRIPTION	"..."
    ::= { fooStringEntry 1 }

fooStringName OBJECT-TYPE
    SYNTAX	OCTET STRING
    MAX-ACCESS  not-accessible
    STATUS	current
    DESCRIPTION "..."
    ::= { fooStringEntry 2 }

fooStringData OBJECT-TYPE
    SYNTAX	Integer32
    MAX-ACCESS  read-only
    STATUS	current
    DESCRIPTION "..."
    ::= { fooStringEntry 3 }


fooOidTable OBJECT-TYPE
    SYNTAX	SEQUENCE OF FooOidEntry
    MAX-ACCESS	not-accessible
    STATUS	current
    DESCRIPTION	"..."
    ::= { libsmiTest014Mib 6 }

fooOidEntry OBJECT-TYPE
    SYNTAX	FooOidEntry
    MAX-ACCESS	not-accessible
    STATUS	current
    DESCRIPTION "..."
    INDEX	{ fooOidAddr, fooOidName }
    ::= { fooOidTable 1 }

FooOidEntry ::= SEQUENCE {
    fooOidAddr	MacAddress,
    fooOidName	OBJECT IDENTIFIER,
    fooOidData	Integer32
}

fooOidAddr OBJECT-TYPE
    SYNTAX	MacAddress
    MAX-ACCESS  not-accessible
    STATUS	current
    DESCRIPTION	"..."
    ::= { fooOidEntry 1 }

fooOidName OBJECT-TYPE
    SYNTAX	OBJECT IDENTIFIER
    MAX-ACCESS  not-accessible
    STATUS	current
    DESCRIPTION "..."
    ::= { fooOidEntry 2 }

fooOidData OBJECT-TYPE
    SYNTAX	Integer32
    MAX-ACCESS  read-only
    STATUS	current
    DESCRIPTION "..."
    ::= { fooOidEntry 3 }


fooOidBarGroup OBJECT-GROUP
    OBJECTS	{ fooData, barData, fooImpliedData, barImpliedData,
		  fooStringData, fooOidData }
    STATUS	current
    DESCRIPTION
	"junk"
    ::= { libsmiTest014Mib 7 }

END
