LIBSMI-TEST-009-MIB DEFINITIONS ::= BEGIN

IMPORTS
    MODULE-IDENTITY
	FROM SNMPv2-SMI
    TEXTUAL-CONVENTION
	FROM SNMPv2-TC
    testMib
        FROM LIBSMI-TEST-MIB;

libsmiTest009Mib MODULE-IDENTITY
    LAST-UPDATED    "200005300900Z"
    ORGANIZATION    
            "TU Braunschweig"
    CONTACT-INFO    
            "        Frank Strauss
             
             Postal: TU Braunschweig
                     Bueltenweg 74/75
                     38106 Braunschweig
                     Germany
             
              Phone: +49 531 391-3283
              EMail: strauss@ibr.cs.tu-bs.de
               http://www.ibr.cs.tu-bs.de/~strauss/"
    DESCRIPTION     
            "This MIB module contains one or more intentional errors,
             and/or unusual contents. Its only purpose is to check
             the abilities of MIB parsers to detect these circumstances.
             
             This MIB module is orginally written in SMIv2 format.
             
             The MIB parser should complain about improper number and
	     bits enumerations.

	     The libsmi parser is expected to report:
LIBSMI-TEST-009-MIB:109: named bit `yellow(128)' may cause interoperability or implementation problems
LIBSMI-TEST-009-MIB:115: named bit `yellow(524280)' exceeds maximum bit position
LIBSMI-TEST-009-MIB:65: redefinition of name `red' in number enumeration
LIBSMI-TEST-009-MIB:71: redefinition of number `3' in number enumeration
LIBSMI-TEST-009-MIB:93: redefinition of name `red' in named bits list
LIBSMI-TEST-009-MIB:99: redefinition of number `3' in named bits list
	    "
    REVISION        "200005300900Z"
    DESCRIPTION     
            "Initial Revision."
    ::= { testMib 9 }

--
-- Test cases for number enumerations:
--

EnumTcTest1 ::= TEXTUAL-CONVENTION
    STATUS	current
    DESCRIPTION
	"Valid enumeration."
    SYNTAX INTEGER { red(1), green(2), blue(3) }

EnumTcTest2 ::= TEXTUAL-CONVENTION
    STATUS	current
    DESCRIPTION
	"Valid enumeration."
    SYNTAX INTEGER { none(-1), red(1), green(2), blue(3) }

EnumTcTest3 ::= TEXTUAL-CONVENTION
    STATUS	current
    DESCRIPTION
	"Invalid enumeration: redefinition of a name."
    SYNTAX INTEGER { none(-1), red(1), green(2), blue(3), red(4) }

EnumTcTest4 ::= TEXTUAL-CONVENTION
    STATUS	current
    DESCRIPTION
	"Invalid enumeration: redefinition of a number."
    SYNTAX INTEGER { none(-1), red(1), green(2), blue(3), yellow(3) }

--
-- Test cases for named bits lists:
--

BitsTcTest1 ::= TEXTUAL-CONVENTION
    STATUS	current
    DESCRIPTION
	"Valid bits enumeration."
    SYNTAX BITS { red(1), green(2), blue(3) }

BitsTcTest2 ::= TEXTUAL-CONVENTION
    STATUS	current
    DESCRIPTION
	"Valid bits enumeration."
    SYNTAX BITS { none(0), red(1), green(2), blue(3) }

BitsTcTest3 ::= TEXTUAL-CONVENTION
    STATUS	current
    DESCRIPTION
	"Invalid bits enumeration: redefinition of a name."
    SYNTAX BITS { red(1), green(2), blue(3), red(4) }

BitsTcTest4 ::= TEXTUAL-CONVENTION
    STATUS	current
    DESCRIPTION
	"Invalid bits enumeration: redefinition of a number."
    SYNTAX BITS { red(1), green(2), blue(3), yellow(3) }

BitsTcTest5 ::= TEXTUAL-CONVENTION
    STATUS	current
    DESCRIPTION
	"Invalid bits enumeration: number may cause interoperability problems."
    SYNTAX BITS { red(1), green(2), blue(3), yellow(128) }

BitsTcTest6 ::= TEXTUAL-CONVENTION
    STATUS	current
    DESCRIPTION
	"Invalid bits enumeration: number too large to represent."
    SYNTAX BITS { red(1), green(2), blue(3), yellow(524280) }

END
