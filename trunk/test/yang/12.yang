// incorrect

// Notes:
// 1. double definition header's statements;
//

module "test12"{
	yang-version '1' {}
	namespace "urn:smilib:params:test9" {}
 	prefix yang-test._8; 
	namespace "urn:smilib:params:test9" {}
 	prefix yang-test._8; 

	yang-version '1' {}
}
