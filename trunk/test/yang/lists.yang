module lists {
	namespace "urn:test:lists";
	prefix "lists";

    container c {
		list interface {
             key "name name     speed1";
			 unique "test/name1";
			 config true;

			 container test {
				 leaf name1 {
				     type string;
				 }
			 }
			 leaf name {
				 config false;
				 type empty;
			 }
			 leaf speed {
				 type enumeration {
				     enum 10m;
				     enum 100m;
				     enum auto;
				 }
			 }
			 leaf observed-speed {
				 type uint32;
				 config false;
			 }
		 }
    }

 	list interface-state1 {
         key " name";
    }

  	list interface-state2 {
         key "name ";
    }   
 
 	list interface-state3 {
         config true;
    }
    
}
